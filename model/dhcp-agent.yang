module dhcp-agent {

    namespace "urn:ietf:params:xml:ns:yang:dhcp-agent";
    prefix da;

    import ietf-inet-types {
        prefix inet;
    }

    organization "Inocybe Technologies";

    contact "Anton Ivanov <anton.ivanov@cambridgegreys.com>";

    description
        "This module contains a set of definitions to control
         a programmable Layer2 switch DHCP agent and/or DHCP Relay.";

    revision 2018-07-19 {
        description "Initial revision.";
    }

    typedef comparison-operation {
        type enumeration {
            enum "==" {
                value 0;
            }
            enum ">=" {
                value 1;
            }
            enum "=<" {
                value 2;
            }
            enum ">" {
                value 3;
            }
            enum "<" {
                value 4;
            }
            enum "&" {
                value 5;
            }
            enum "|" {
                value 6;
            }
            enum "*" {
                description
                    "Return true regardless of values - intended for additions";
                value 7;
            }
        }
    }

    typedef which-direction {
        type enumeration {
            enum "UP" {
                description "To Server";
                value 0;
            }
            enum "DOWN" {
                description "To Client";
                value 1;
            }
        }
    }
    grouping dhcp-option {
        description "Format of DHCP options"; 
        leaf dhcp-option-code {
            type uint8;
            mandatory true;
            description "DHCP Option Code";
        }
        choice option-type {
            case void-option {
            }
            case inet-option {
                leaf inet {
                    type inet:ipv4-address;
                    description "An IPv4 Address";
                }
            }
            case inet-list {
                list inets {
                    key "order";
                    description "A list of IPv4 Addresses";
                    leaf order {
                        type uint8; 
                        description "Dummy number used to order the list";
                    }
                    leaf address {
                        type inet:ipv4-address;
                        description "An IPv4 Address";
                    }
                }
            }
            case inet-paired-list {
                list paired-inets {
                    key "order";
                    description "A list of IPv4 Addresses";
                    leaf order {
                        type uint8; 
                        description "Dummy number used to order the list";
                    }
                    leaf address-1 {
                        type inet:ipv4-address;
                        description "An IPv4 Address";
                    }
                    leaf address-2 {
                        type inet:ipv4-address;
                        description "An IPv4 Address";
                    }
                }
            }
            case integer {
                leaf int-value {
                    type uint32; 
                    description "32 bit integer value";
                }
            }
            case short {
                leaf short-value {
                    type uint16; 
                    description "16 bit integer value";
                }
            }
            case short-list {
                leaf-list short-value-list {
                    type uint16; 
                    description "list of 16 bit integer values";
                }
            }
            case byte {
                leaf byte-value {
                    type uint8; 
                    description "8 bit integer value";
                }
            }
            case byte-list {
                leaf-list byte-value-list {
                    type uint8; 
                    description "List of 8 bit integer values";
                }
            }
            case string {
                leaf-list string-value {
                    type string; 
                    description "String option value";
                }
            }
            case relays {
                list relay-option-values {
                    key "relay-option";
                    description "A list of Relay Agent Options";
                    leaf relay-option {
                        type uint8; 
                        description "Relay Option Code";
                    }
                    leaf value {
                        type string;
                        description "Relay Option Value";
                    }
                }
            }
            case client-identifier {
                container ids {
                    leaf hardware-type {
                        type uint8;
                        description "Hardware Type"; 
                    }
                    leaf string {
                        type string; 
                        description "Hardware address";
                    }
                }
            }
            
            case csr {
                leaf csr {
                    type inet:ipv4-prefix; 
                    description "IPv4 Prefix (leave the conversion to serialization)"; 
                }
            }
            case binary {
                leaf bin-value {
                    type binary;
                    description "Catch-all for everything else which we do not know";
                }
            }
            /*
            suboptions : hex encoded sub options
            */
        }
    }

    grouping dhcp-packet {
        description "Format of DHCP Packet";
        leaf op {
            type uint8;
            description "BOOTP op";
        }
        leaf htype {
            type uint8;
            description "Hardware Type";
        }
        leaf hlen {
            type uint8;
            description "Hardware Address Length";
        }
        leaf hops {
            type uint8;
            description "Relay Agent Hops";
        }
        leaf xid {
            type uint32;
            description "Xid";
        }
        leaf secs {
            type uint16;
            description "Seconds since the start of configuration";
        }
        leaf flags {
            type uint16;
            description "Flags - Broadcast or Unicast for reply";
        }
        leaf ciaddr {
            type inet:ipv4-address;
            description "Client IP Address";
        }
        leaf yiaddr {
            type inet:ipv4-address;
            description "Your (client) IP address";
        }
        leaf siaddr {
            type inet:ipv4-address;
            description "Next Server address";
        }
        leaf giaddr {
            type inet:ipv4-address;
            description "Relay Address";
        }
        leaf chaddr {
            type binary;
            description "Client Hardware Address";
        }
        leaf sname {
            type string;
            description "Server Name";
        }
        leaf file {
            type string;
            description "Boot File Name";
        }
        list dhcp-options {
            key "option-order";
            leaf option-order {
                type uint8;
                description "Dummy ordering field to order the list";
            }
            uses dhcp-option;
        }
    }

    grouping comparison-data {
        leaf operation {
            type comparison-operation;
            description "Operation for comparison";
        }

        leaf list-operation {
            type comparison-operation;
            description "Operation for comparison - list form options";
        }

        leaf direction {
            type which-direction;
            description "When to apply the processing";
        }

        uses dhcp-packet;
    }



    /*
    * Configuration data nodes
    */

    container interfaces {
        description
            "Interface configuration parameters.";

        list interface {
            key "name";

            description
                "The list of interfaces where the DHCP agent listens for
                 DHCP requests.";


            leaf name {
                type string;
                description
                    "The name of the interface.";
            }
            choice upstream {
                case relay {
                    leaf-list dhcp-servers {
                        type inet:domain-name;
                        description
                            "A set of servers to forward requests for this interface when
                             operating as a DHCP Relay.
                             The domain name will be looked up only using the ipv4 address family.";
                        min-elements 1;
                    }
                }
                case mitm {
                    leaf-list trusted-interfaces {
                        type string;
                        description
                            "A set of trusted interfaces when operating in DHCP snooping mode";
                        min-elements 1;
                    }
                }
            } 
            leaf query-policy {
                description    "Operating method for upstream servers/interfaces.";
                type enumeration {
                    enum round-robin { value 0;}
                    enum replicate { value 1;}
                }
            }

            list delete {
                key "priority";
                description 
                "Options to delete

                 The implementation scans the dhcp data and selects an
                 an option to delete. 

                 Specifying only the option code will delete 
                 regardless of value and comparison operation. 

                 Specifying option values will use the 
                 comparison-operation from op on the option data.
                 If the option data is a list, the operation will be
                 performed on all elements and accumulated according
                 to list-op.
                 If the comparison operation yields a true value, the
                 option will be deleted.
                ";
                leaf priority {
                    type uint32;
                    description "Defines the order in which the rules are executed";
                }
                uses comparison-data;

            }
            list add {
                key "priority";
                description 
                "Options to add
                 The implementation scans the dhcp data using the same semantics as for
                 delete. If the search returns true, the list of additions is executed.
                ";
                leaf priority {
                    type uint32;
                    description "Defines the order in which the rules are executed";
                }
                
                uses comparison-data;

                list additions {
                    key "order";
                    leaf order {
                        type uint32;
                        description "Defines the order in which the additions are processed";
                    }
                    uses dhcp-packet;
                }
            }
        }
    }
}
